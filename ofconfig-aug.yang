module ofconfig-aug
{
  namespace  "urn:bcm:ofdpa10:accton01";   
  prefix ofdpa10;  
  
  import of-config1.1.1{ prefix "of11-config"; }
  import ietf-yang-types { prefix yang; } 
  import ietf-inet-types { prefix inet; }
	  
  organization "ACCTON";
  contact "xxx@accton.com";
  
  description "OFconfig port will exec 'of-agent vtap lport ethernet ethernet [vid vid]' + 'of-agent vtep lport vni vni'
               or 'of-agent vtep lport source source-ip destination destination-ip udp-source-port port' + 
			   'of-agent vtep lport vni vni' ";
    
  revision 2015-01-17 { 
      description "First Version";

      reference "www.onf.org";
  }

  augment "/of11-config:capable-switch/of11-config:resources/of11-config:port" {

	container vtap
	{
      presence "Configures VxLAN tunnel access settings";
	  description "VxLAN tunnel access port";
	  
  	  leaf phy-port{
	    type uint32;
        mandatory true;
	    description "VxLAN access physical port";
	  }
	  leaf vid{
	    type uint32;
	    description "VxLAN access VLAN ID. With phy-port and vid it can associated to a specific VNI."; 
	  }
      leaf vni {
        type leafref {
            path  "/of11-config:capable-switch/ofdpa10:vni/ofdpa10:id";
        }
	    description "ID for creating VxLAN tunnel.";
      }	  
	}

	container vtep
	{
      presence "Configures VxLAN tunnel endpoint settings";
	  description "VxLAN tunnel endpoint port";

      leaf src-ip{
        type inet:ipv4-address;
        mandatory true;
		description "Specifies source IP address for origination packets or destination IP address for termination packets";
	  }
      leaf dest-ip{
        type inet:ipv4-address;
        mandatory true;
		description "Specifies destination IP address for unicast origination packets or source IP address for termination packets";
	  }
      leaf udp-src-port {
	    type inet:port-number;
        mandatory true;
		description "Specifies UDP source port for VXLAN";
	  }
      leaf nexthop-id {
        type leafref {
            path  "/of11-config:capable-switch/ofdpa10:next-hop/ofdpa10:id";
        }
	    description "Specifies tunnel nexthop ID";
      }
	  leaf ecmp-id {
        type leafref {
            path  "/of11-config:capable-switch/ofdpa10:ecmp/ofdpa10:id";
        }
	    description "Specifies ECMP ID";
	  }
	  leaf ttl {
	    type uint32;
	    description "Specifies TTL value of packets";
	  }
      leaf vni {
        type leafref {
            path  "/of11-config:capable-switch/ofdpa10:vni/ofdpa10:id";
        }
	    description "ID for creating VxLAN tunnel.";
      }
	}

  }

  augment "/of11-config:capable-switch" {
	leaf udp-dest-port {
	    type inet:port-number;
		description "Globally configure VxLAN UDP destination port";
	}
	
	leaf udp-src-port-entropy {
	    type boolean;
		description "Globally configure VxLAN UDP srouce port use entroy port number.
		             When enable this, all VxLAN UDP source port will be generated by CHIP vendor.";
	}
  
	list vni
	{
	    description "Create a tunnel";
	    key id;	
        leaf id {
          type uint32;
		  mandatory true;
	      description "ID for creating VxLAN tunnel.
	                  for 'of-agent vni vni'";
        }	
	    leaf vni-multicast-group{
	      type inet:ip-address;
	      description "Specifies this VNI broadcast and multicast use which multicast group for VxLAN.
		               'of-agent vni vni multicast-group nexthop-id' ";
	    }	
		
	    leaf multicast-group-nexthop-id{
          type leafref {
            path  "/of11-config:capable-switch/ofdpa10:next-hop/ofdpa10:id";
          }
	      description "Specifies tunnel nexthop ID";
		}
	}
		
	list next-hop{
	    key id;
		description "Configure the physical port for VxLAN logical port to ouput packet.";		
	    leaf id{
		  type uint32;
		  mandatory true;
	      description "Specifies tunnel nexthop ID.
	                  for 'of-agent nexthop id'";
		}
        leaf dest-mac{
		   type yang:mac-address;
           mandatory true;
		   description "packet output Destination MAC";
		}
		leaf phy-port{
		   type uint32;
           mandatory true;
		   description "packet output physical port";
		}
		leaf vid{
		   type uint32;
           mandatory true;
           description "packet output VLAN ID";		   
		}
	}
	
	list ecmp{
	    key id;
		description "create ECMP group";
	    leaf id{
		  type uint32;
		  mandatory true;
	      description "Specifies ECMP ID.
	                  for 'of-agent ecmp id'";
		}
        leaf-list nexthop-id {
          type leafref {
            path  "/of11-config:capable-switch/ofdpa10:next-hop/ofdpa10:id";
          }
        }		
	}
  }
}
